// vi: set smarttab et sw=4 tabstop=4:
module sfc-monitor-impl {

  yang-version 1;
  namespace "urn:opendaylight:params:xml:ns:yang:controller:config:sfc-monitor:impl";
  prefix "sfc-monitor-impl";

  import config { prefix config; revision-date 2013-04-05; }
  //import rpc-context { prefix rpcx; revision-date 2013-06-17; }
  //import opendaylight-md-sal-binding { prefix mdsal; revision-date 2013-10-28; }


  description
      "This module contains the base YANG definitions for
      sfc-monitor impl implementation.";

  revision "2016-05-06" {
      description
          "Initial revision.";
  }

  // This is the definition of the service implementation as a module identity
  identity sfc-monitor-impl {
      base config:module-type;

      // Specifies the prefix for generated java classes.
      config:java-name-prefix SfcMonitor;
  }




  rpc trace-sfc {
      description
        "Get SFC path trace information";
      output {
        leaf result {
         type string;
         description
         "trace";
         }
      }
    }
    rpc clean-trace-sfc {
        description
          "clean SFC path trace information";
      }
}
